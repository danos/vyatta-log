module vyatta-system-journal-v1 {
    namespace "urn:vyatta.com:mgmt:vyatta-system-journal-v1";
    prefix vyatta-system-journal-v1;

    import configd-v1 {
        prefix configd;
    }

    import vyatta-system-v1 {
        prefix system;
    }

    import vyatta-types-v1 {
        prefix types;
    }

    organization "AT&T Inc.";
    contact
        "AT&T
         Postal: 208 S. Akard Street
                 Dallas, TX  75202
         Web:    www.att.com";

    description
        "Copyright (c) 2018-2020, AT&T Intellectual property.
         All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

         The YANG module for vyatta-system-journal-v1

         Root configuration node for all options related to the
         configuration of systemd-journal via the Vyatta Configuration CLI.";

	revision 2021-03-11 {
		description "Replace default static journal max size";
	}

    revision 2020-05-19 {
        description "Add storage size configuration";
    }

    revision 2019-07-31 {
        description "Refactor 'journal export' into a grouping";
    }

    revision 2018-08-15 {
        description "Add 'rate-limit' configuration commands";
    }

    revision 2018-01-12 {
        description "Initial revision - v1";
    }

    grouping journal-rate-limit {
        container rate-limit {
            description "Configures the maximum burst size (in number of log
                         entries) allowed within the interval specified. Log
                         entries will be suppressed if the number of log
                         entries exceeds the burst value within the specified
                         interval.";
            presence "Enable rate-limit";
            configd:help "Enable log rate limiting";
            configd:end "vyatta_update_journal.pl";
            leaf interval {
                type types:time-interval-seconds;
                configd:help "Interval in seconds";
                default "30";
                description "Specifies the rate limit interval in seconds.
                             If the number of log entries exceeds the burst
                             value within this interval logging will be
                             suppressed.";
            }
            leaf burst {
                type uint32 {
                    configd:help "Number of log entries in interval";
                }
                configd:help "Number of log entries in interval";
                default "1000";
                description "Specifies the maximum number of log entries
                             allowed within the specified interval before
                             logs are suppressed";
            }
        }
    }

    grouping journal-storage {
        container storage {
            configd:help "Configure journal storage";
            description "Configure journal storage";
            leaf size {
                type union {
                    type string {
                        configd:help "Maximum amount of journal storage";
                        pattern '[1-9][0-9]*[KMGT]?';
                        configd:pattern-help "<num>[suffix(K,M,G,T) Bytes otherwise]";
                    }
                    type string {
                        pattern 'auto';
                        configd:help "Allow the system to detemine the best size for the journal";
                        configd:pattern-help "auto";
                    }
                }
                default "auto";
                description "Specifies the maximum amount of file-system space
                             that may be used for storing journal messages.
                             The system will determine the best value for the journal's
                             maximum size, currently it uses 10% of the log partition up to 4GB.
                             This may change in the future.
                             Using the default means that this behavior is acceptable.";
                configd:help "Maximum amount of file-system space for journal storage";
            }
            configd:end "vyatta_update_journal.pl";
        }
    }

    grouping journal-config {
        container journal {
            configd:help "Systemd Journal configuration options";
            description  "Systemd Journal configuration options";
            container export {
                configd:help "Configure log exports from systemd-journal";
                description "Configuration for log exports from systemd-journal";
            }
        }
    }

    augment /system:system {
        uses journal-config {
            augment journal {
               uses journal-rate-limit;
               uses journal-storage;
            }
        }
    }
}
